package jdehart_ModelExample_A {
    import ScalarValues::*;

    part def Automobile;
    alias Automobile as Car;
    
    part def Aeroplane;
    alias Aeroplane as Jet;
    
    part def Bicycle{
        part def Wheel;
    }
}
